module Accedian-session-echo {
  yang-version 1.1;
  namespace "http://accedian.com/ns/yang/session/echo";
  prefix acdsecho;

  import ietf-inet-types {
    prefix inet;
  }

  import Accedian-net-type {
    prefix acdnt;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "The Echo session type supports ping-like echo sessions
    over UDP or ICMP.

    Copyright (c) Accedian Networks, Inc.
    All rights reserved";

  revision 2025-06-30 {
    description
      "Initial revision";
  }

  augment "/acdses:sessions/acdses:session/acdses:service-endpoints/acdses:session-protocol" {
    when "derived-from-or-self(/acdses:sessions/acdses:session/acdses:session-type, 'acdstype:echo')";
    description
      "Augment the service session protocol of Accedian-service-session with echo
      config data";

    container echo {
      description
        "Echo session configuration data";

      leaf protocol-type {
        type enumeration {
          enum "icmp" {
            description
              "Echo session over the ICMP protocol";
          }
          enum "udp" {
            description
              "Echo session over the UDP protocol";
          }
        }
        default "udp";
        description
          "Echo session protocol type";
      }

      container session-sender {
        description
          "Echo packet sender configuration data";

        leaf admin-state {
          type boolean;
          default false;
          description
            "Indicates whether the associated session
            endpoint is operating as a echo packet
            sender";
        }

        leaf sender-ip {
          type inet:ip-address;
          description
            "The IP address of the sender interface.
            If not specified, the packets will be sent using
            the sender local network configuration";
        }

        leaf reflector-ip {
          type inet:ip-address;
          description
            "The IP address of reflector interface.
            If not specified, the address configured in the
            associated session endpoint will be used. If a
            peered endpoint is not defined or if the peer doesn't
            specify an address, an error will be returned";
        }

        container udp {
          when "../../protocol-type = 'udp' and ../admin-state = 'true'";

          leaf sender-udp-port {
            type acdnt:source-port-number;
            description
              "The UDP port number to use as a source UDP port";
          }

          leaf reflector-udp-port {
            type inet:port-number;
            description
              "This parameter defines the UDP port number used by the
              Session-Sender as the UDP destination port for this ECHO-Test session. It is
              used in scenarios where the transmitted destination port must be different from
              the port value expected by the session-reflector. This is typically required
              on network paths where the destination port is translated to a different value. For
              example, with NAT and/or port forwarding.

              If a value for this field is not provided, the value configured
              in session-reflector/udp/reflector-udp-port will be used";
          }
        }

        leaf report-interval {
          type uint16 {
            range "1..900";
          }
          units seconds;
          default 30;
          description
            "Reporting interval";
        }

        container test-packets {
          description
            "Echo packet configuration data";

          leaf payload-size {
            type uint16 {
              range "20..1472";
            }
            units bytes;
            default 82;
            description
              "Echo test packet payload size";
          }

          leaf rate {
            type uint16 {
              range "1..1000";
            }
            units packets-per-second;
            default 10;
            description
              "Echo packet rate";
          }

          leaf dscp {
            type acdnt:dscp;
            description
              "The DSCP value present in the IP header of the Echo test packet";
          }

          leaf ttl {
            type acdnt:ttl;
            description
              "The Time To Live value present in the IP header of the Echo test packet";
          }

          leaf vlan-priority {
            type acdnt:vlan-prio;
            description
              "Vlan priority used when the test packet is sent with a VLAN tag";
          }
        }
      }

      container session-reflector {
        description
          "Echo packet reflector configuration data";

        leaf admin-state {
          type boolean;
          default false;
          description
            "Indicates whether the associated session
            endpoint is operating as a echo session
            reflector";
        }

        container udp {
          when "../../protocol-type = 'udp' and ../admin-state = 'true'";
          leaf reflector-udp-port {
            type inet:port-number;
            default 7;
            description
              "This parameter defines the UDP port number binded by the echo
              reflector server";
          }
        }
      }
    }
  }
}
