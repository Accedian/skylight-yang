module Accedian-service-endpoint-ssc {
  yang-version 1.1;
  namespace "http://accedian.com/ns/yang/service/endpoint/ssc";
  prefix acdsepssc;

  import Accedian-service-endpoint-type {
    prefix acdsept;
  }

  import Accedian-service-endpoint {
    prefix acdsep;
  }

  import Accedian-extensions {
    prefix acdext;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of a Accedian Skylight Sensor
    Control (SSC) endpoint.
    It augments the definition of the top level Accedian endpoint.

    Copyright (c) Accedian Networks, Inc.
    All rights reserved";

  revision 2023-11-24 {
    description
      "Initial revision";
  }

  augment "/acdsep:service-endpoints/acdsep:service-endpoint/acdsep:config" {
    when "derived-from-or-self(/acdsep:service-endpoints/acdsep:service-endpoint/acdsep:type, 'acdsept:ssc-endpoint')" {
      description
        "Augment Accedian service-endpoint data with Skylight Sensor Control (SSC) support";
    }

    container ssc-config {
      description
        "The configuration elements of a SSC type service endpoint";

      leaf interface-id {
        type string;
        acdext:tag-metadata interface_id;
        description
          "The string identifying the interface instance";
      }

      leaf sensor-control-id {
        type string;
        description
          "The string identifying the Sensor Control (VCX) instance";
      }
    }
  }
}
