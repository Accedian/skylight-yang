module Accedian-session-y1564 {
  yang-version 1.1;
  namespace "http://accedian.com/ns/yang/session/sat/y1564";
  prefix acdsy;

  import ietf-yang-types {
    prefix yang;
  }

  import ietf-inet-types {
    prefix inet;
  }

  import Accedian-net-type {
    prefix acdnt;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition for the Accedian SAT Y1564 protocol.

    Y.1564 tests support standardized testing for turning up, installing and troubleshooting Ethernet-based
    services. This Yang file describes the model to set up Y.1564 in order to perform end-to-end Ethernet
    service activation tests.
    You can run a Y.1564 test to determine the conformance of a network section or a specific device to a service
    level agreement (SLA) and/or to meet Ethernet standards. You can define a total of eight flows per
    test. See the ITU-T Y.1564 standard for the definition of parameters and tests

    Copyright (c) Accedian Networks, Inc.
    All rights reserved";

  revision 2024-08-31 {
    description
      "Initial revision";
  }

  typedef measurement-type {
    description
      "The type of measurement to perform. Can be measured
      based on maximum values or based on an average";

    type enumeration {
      enum max-value {
        description
          "Maximum value based measurement";
      }
      enum average-value {
        description
          "Average value based measurement";
      }
    }
  }

  typedef frame-size-type {
    type enumeration {
      enum fixed {
        description
          "Fixed frame size";
      }
      enum emix {
        description
          "For EMIX, rhe size of the test packets will follow the
          sequence based on frame sizes a, b, c, d, e, f, g, and u,
          where: a=64Bytes, b=128Bytes, c=256Bytes, d=512Bytes,
          e=1024Bytes, f=1280Bytes, g=1518Bytes.
          u is the user-defined size";
      }
    }
  }

  augment "/acdses:sessions/acdses:session/acdses:service-endpoints/acdses:session-protocol" {
    when "derived-from-or-self(/acdses:sessions/acdses:session/acdses:session-type, 'acdstype:y1564')";
    description
      "Augment the service session protocol of Accedian-service-session with SAT
      config data";

    container y1564 {
      description
        "Configuration data and reports for the Y.1564 SAT protocol";

      leaf transport-type {
        type acdnt:transport-type;
        default layer3;
        description
          "Session transport type";
      }

      container session-sender {
        description
          "Configuration data for the Y.1564 sender";

        leaf admin-state {
          type boolean;
          default false;
          description
            "Indicates whether the associated session
            endpoint is operating as a Y.1564 sender";
        }

        leaf outgoing-port-name {
          type acdnt:logical-port;
          description
            "Session sender outgoing interface. Depending
            on the platform this could be a physical port name
            or a NFV-interface/virtual-connection name

            If an outgoing port name is not specified here, the port
            configured in the endpoint of the session-sender will
            be used.
            If a port is not specified here and the endpoint configuration
            does not specify a port, an error will be returned";
        }

        container layer2 {
          when "../../transport-type = 'layer2' and ../admin-state = 'true'";

          leaf y1731-meg-level {
            type acdnt:y1731-meg-level;
            description
              "Y.1731 Maintenance Entity Group level";
          }
        }

        container layer3 {
          when "../../transport-type = 'layer3' and ../admin-state = 'true'";

          leaf source-udp-port {
            type acdnt:source-port-number;
            mandatory true;
            description
              "The UDP port number that is to be used by
              the sender for this Y.1564 session";
          }

          leaf dscp {
            type acdnt:dscp;
            description
              "The DSCP value present in the IP header of the
              Y.1564 Test Layer-3 packets";
          }
        }

        container test-config {
          description
            "Test configuration data";

          leaf step-duration {
            type uint8 {
              range "1..60";
            }
            units seconds;
            default 10;
            description
              "Duration of each step during the configuration test";
          }

          leaf parallel-test-enable {
            type boolean;
            default true;
            description
              "Enable Y.1564 parallel service configuration test";
          }

          leaf test-duration {
            type uint16 {
              range "1..1440";
            }
            units minutes;
            default 15;
            description
              "Duration of each step during the performance test";
          }
        }

        list service {
          key service-name;
          ordered-by user;
          max-elements 8;
          description
            "A list of ITU-Y1564 services";

          leaf service-name {
            type string;
            description
              "The name of this specific service";
          }

          leaf frame-size-type {
            type frame-size-type;
            default "fixed";
            description
              "Packet sizes may be fixed or EMIX. Fixed packet size
              is specified by the fixed-packet-size field";
          }

          leaf fixed-packet-size {
            when "../frame-size-type = 'fixed'";
            type uint16 {
              range "64..10240";
            }
            units bytes;
            default 512;
            description
              "Specify packet size when size-type is 'fixed'. Maximum packet
              size is 10240";
          }

          leaf emix-size-sequence {
            when "../frame-size-type = 'emix'";
            type string {
              length "1..8";
              pattern '[abcdefgu]+';
            }
            default "bceg";
            description
              "Specify the EMIX sequence of packet sizes for the test";
          }

          leaf emix-user-packet-size {
            when "../frame-size-type = 'emix'";
            type uint16;
            default 2000;
            description
              "For a user-defined packet (u), specify the packet size";
          }

          leaf cir {
            type decimal64 {
              range "0.0..10000.0" {
                description
                  "0 to 10000 (0 to 10 Gbps) on ports supporting a maximum of 10Gbps.
                  0 to 1000 (0 to 1 Gbps) on ports supporting a maximum of 1Gbps.
                  In steps of 0.125 Mbps for rates
                  from 0 to 12.5 Mbps, and in steps of 1 Mbps for rates greater
                  than or equal to 13 Mbps";
              }
              fraction-digits 3;
            }
            units megabits-per-second;
            default 10.0;
            description
              "Committed information rate. The maximum value here depends on the
              port/device speed. A value beyond the maximum speed will return
              an error";
          }

          leaf eir {
            type decimal64 {
              range "0.0..10000.0" {
                description
                  "0 to 10000 (0 to 10 Gbps) on ports supporting a maximum of 10Gbps.
                  0 to 1000 (0 to 1 Gbps) on ports supporting a maximum of 1Gbps.
                  In steps of 0.125 Mbps for rates
                  from 0 to 12.5 Mbps, and in steps of 1 Mbps for rates greater
                  than or equal to 13 Mbps";
              }
              fraction-digits 3;
            }
            units megabits-per-second;
            default 3.0;
            description
              "Excess information rate. The maximum value here depends on the
              port/device speed. A value beyond the maximum speed will return
              an error";
          }

          leaf fdv {
            type uint32 {
              range "0..2147483647";
            }
            units microseconds;
            default 1000;
            description
              "Maximum/average two-way Frame Delay Variation (FDV)
              allowed";
          }

          leaf fdv-type {
            type measurement-type;
            default max-value;
            description
              "Determines whether the Frame Transfer Delay (FTD) parameter
              is a maximum or average value";
          }

          leaf flr {
            type decimal64 {
              fraction-digits 10;
              range "0.0000000001..0.999";
            }
            units ratio;
            default 0.000001;
            description
              "Maximum Frame Loss Ratio (FLR) allowed.
              Note: The ratio is the maximum faction of frame that can be dropped
              without failing. Example 0.5 ratio mean that less than 50% of the
              frame are dropped.";
          }

          leaf ftd {
            type uint32 {
              range "0..2147483647";
            }
            units microseconds;
            default 5000;
            description
              "Maximum/average two-way Frame Transfer Delay (FTD)
              allowed";
          }

          leaf ftd-type {
            type measurement-type;
            default "max-value";
            description
              "Determines whether the Frame Transfer Delay (FTD) parameter
              is a maximum or average value";
          }

          leaf m-factor {
            type decimal64 {
              fraction-digits 3;
              range "0.001..1000.0";
            }
            units megabits-per-second;
            default 1.0;
            description
              "The M factor is added to the Service Acceptance Criteria in the
              policing test to take into account the effect of the CBS and EBS
              on the total rate. The policing test will pass if IR-T=<CIR+EIR+M
              Where: IR-T: Total Information Rate
              CIR: Committed Information Rate
              EIR: Excess Information Rate
              M: M factor (default value = 1 Mbps)";
          }

          leaf out-of-order {
            type uint8 {
              range "0..100";
            }
            units percentage;
            description
              "Maximum out-of-order packets rate allowed";
          }

          leaf availability {
            type boolean;
            default false;
            description
              "When set to true, enable Availability measurement";
          }

          leaf policing {
            type boolean;
            default true;
            description
              "When set to true, enable policing testing";
          }

          leaf step-load {
            type boolean;
            default false;
            description
              "When set to true, enable step testing";
          }

          container vlan-1 {
            presence "Present when tagging a single vlan or when tagging an inner vlan in a vlan-in-vlan configuration.";
            uses acdnt:vlan-config;
            description
              "Inner VLAN configuration";
          }

          container vlan-2 {
            presence "Present when tagging an outer vlan in a vlan-in-vlan configuration.";
            must "../vlan-1" { error-message "vlan-2 can only be configured if vlan-1 is also configured."; }
            uses acdnt:vlan-config;
            description
              "Outer VLAN configuration";
          }

          container config-override {

            container layer2 {
              when "../../../../transport-type = 'layer2'";

              leaf mac-address {
                type yang:mac-address;
                description
                  "The reflector MAC address";
              }

              leaf y1731-meg-level {
                type acdnt:y1731-meg-level;
                description
                  "Y.1731 Maintenance Entity Group level";
              }
            }

            container layer3 {
              when "../../../../transport-type = 'layer3'";

              leaf ip {
                type inet:ip-address;
                description
                  "The IPv4 or IPv6 reflector address";
              }

              leaf dscp {
                type inet:dscp;
                description
                  "The DSCP value present in the IP header of the
                  Y.1564 Test Layer-3 packets";
              }
            }
          }
        }
      }

      container session-reflector {
        description
          "Configuration data for the Y.1564 reflector";

        leaf admin-state {
          type boolean;
          default false;
          description
            "Indicates whether the associated session
            endpoint is operating as a Y.1564 reflector";
        }

        container layer2 {
          when "../../transport-type = 'layer2' and ../admin-state = 'true'";

          leaf mac-address {
            type yang:mac-address;
            description
              "The reflector MAC address

              If a MAC address is not specified here, the MAC address configured
              in the endpoint of the session-reflector will be used.
              If the endpoint configuration does not specify a MAC address, an
              error will be returned";
          }
        }

        container layer3 {
          when "../../transport-type = 'layer3' and ../admin-state = 'true'";

          leaf ip {
            type inet:ip-address;
            mandatory true;
            description
              "The IPv4 or IPv6 reflector address";
          }

          leaf destination-udp-port {
            type inet:port-number;
            mandatory true;
            description
              "This parameter defines the destination UDP port number
              expected by the reflector for this Layer-3 SAT session";
          }
        }
      }

      container reports {
        config false;
        description
          "Status data related to Y.1564 generated reports";

        leaf-list available-reports {
          type string;
          description
            "Returns the list of reports available from current
            and past Y.1564 tests.
            Reports can be fetched and managed through the RPCs
            defined in the Accedian-sat module";
        }
      }
    }
  }
}
