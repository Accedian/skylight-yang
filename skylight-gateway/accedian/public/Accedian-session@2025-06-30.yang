module Accedian-session {
  yang-version 1.1;
  namespace "http://accedian.com/ns/yang/session";
  prefix acdses;

  import Accedian-type {
    prefix acdt;
  }

  import Accedian-session-type {
    prefix acdst;
  }

  import Accedian-service-endpoint {
    prefix acdsep;
  }

  import Accedian-extensions {
    prefix acdext;
  }

  import Accedian-metadata {
    prefix acdmeta;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the definition of an Accedian service
    session. It is session-protocol and service-endpoint data agnostic
    by design.

    Session protocol specific models are added through session protocol
    modules. Their implementation is contained in modules following the
    format: Accedian-session-<proto>.yang. They augment the service
    model when sessions:type match.

    Session endpoints are specified by refering to pre-existing endpoint IDs.

    Copyright (c) Accedian Networks, Inc.
    All rights reserved";

  revision 2025-06-30 {
    description
      "Add force-delete RPC support.
      Fix topology length";
  }

  revision 2024-08-31 {
    description
      "Add metadata container.
      Remove the autostart leaf. It was never implemented";
  }

  revision 2023-11-24 {
    description
      "Make the leaf session-type mandatory";
  }

  revision 2023-06-23 {
    description
      "Add the session group-id field";
  }

  revision 2023-02-10 {
    description
      "Initial revision ";
  }

  notification state-change-event {
    description
      "This notification is sent when the state of the session changes";

    leaf session-id {
      type acdt:id;
      description
        "An identifier specifying on which session the state-change happened. This
        leaf will match the name of an existing session ID (i.e the value
        of /sessions/session/session-id)";
    }

    leaf group-id {
      type acdt:id;
      description
        "The value of the Group ID configured in Accedian-session:sessions:session:group-id.
        The value will be present only if the value was configured in the session
        associated with state-change-event:session-id";
    }

    uses acdst:service-session-state-data;
  }

  container sessions {
    list session {
      description
        "A list of all the configured sessions. The sessions are identified by
        a session id";
      key session-id;
      unique session-name;

      leaf session-id {
        type acdt:id;
        acdext:tag-metadata session_id;
        description
          "Unique identifier for the session.
          tag-metadata: This leaf will be included as part of the analytics
          metadata as { session_id : <session-id> }";
      }

      leaf session-name {
        type acdt:id;
        acdext:tag-metadata session_name;
        description
          "An optional human readable session name. When provided, the field must
          be unique through all the 'list session' instances.
          'session-name' can be used as an extra metadata query parameter in
          analytics in addition to the session-id. It can also be configured
          to query more easily the analytics when the session-id is in non-human
          readble form (numerical, UUIDs, etc...).
          tag-metadata: This leaf will be included as part of the analytics
          metadata as { session_name : <session-name> }";
      }

      leaf group-id {
        type acdt:id;
        description
          "An optional group identifier that associates this session to a logical group of
          sessions. The yang client can associate a session to a group of sessions by configuring
          the same group-id in all the sessions belonging to that group. These groupings can then
          be used to perform operations on all sessions belonging to a group. It can also be used
          to register to event stream resources based on the group-id";
      }

      leaf description {
        type string;
        description
          "An optional human readable description for this session";
      }

      leaf session-type {
        type identityref {
          base acdst:session;
        }
        mandatory true;
        description
          "The type of service configured for this session";
      }

      list service-endpoints {
        description
          "The list of service endpoints involved in the session.";
        key endpoint-id;

        leaf endpoint-id {
          type leafref {
            path "/acdsep:service-endpoints/acdsep:service-endpoint/acdsep:endpoint-id";
          }
          description
            "A reference to the service endpoint unique identifier";
        }

        container session-protocol {
          description
            "Protocol/session-service specific configuration for this endpoint. The configuration
            is dependent on the session protocol type specified in /sessions/session/session-type.
            It is Implemented as a Yang augment mount point";
        }
      }

      container status {
        config false;
        uses acdst:service-session-state-data;
      }

      action start {
        description
          "This action will start the session";
      }

      action stop {
        description
          "This action will stop the session";
      }

      container metadata {
        description
          "Metadata for this session. Custom metadata and topology metadata can be
          provided for each session";

        uses acdmeta:metadata-list;

        leaf-list topology {
          type string {
            length 1..100;
          }
          max-elements 25;
          ordered-by user;
          description
            "String tags used to describe the path segments associated with this session.
            The user is responsible to order the list according to the represented session
            topology";
        }
      }
    }
  }

  rpc force-delete {
    description
      "A remote procedure call that forces the deletion of a session at the yang datastore level. This RPC will
      first attempt to delete the session using the normal delete mechanism (i.e same as restconf-delete). But
      contrary to the normal delete, if a subsystem-dependent-error occurs during the deletion, the session will
      be deleted anyway from the yang datastore.

      Note: This RPC does not allow to force-delete an instance that is referred by another yang-datastore instance.
      For example: attempting to force-delete a session referred by a Accedian-service won't be deleted and will
      return an error. The yang-level datastore dependencies must be deleted first before attempting to force-delete
      a session.

      *** WARNING ***
      This RPC is not intended for normal operations and should only be used as a last resort. Force-deleting an
      instance from the datastore can cause a configuration inconsistency between the dependent subsystems";

    input {
      leaf session-id {
        type acdt:id;
        mandatory true;
        description
          "The session-id of the session instance to force-delete";
      }
    }
  }
}
