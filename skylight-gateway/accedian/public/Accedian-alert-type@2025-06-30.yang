module Accedian-alert-type {
  yang-version 1.1;
  namespace "http://accedian.com/ns/yang/alert/type";
  prefix acdalt;

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "Accedian yang model Skylight Alarms.

    Copyright (c) Accedian Networks, Inc.
    All rights reserved";

  revision 2025-06-30 {
    description
      "Add metric-baseline policy type";
  }

  revision 2024-08-31 {
    description
      "Initial revision";
  }

  identity alert-policy {
    description
      "The base type identifying a Accedian alert policy";
  }
    
  identity metric {
    base alert-policy;
    description
      "Alerts policies based on metric values and constraints";
  }

  identity metric-baseline {
    base alert-policy;
    description
      "Alerts policies based on baseline values";
  }

  typedef alert-severity {
    description
      "Severity of the alert";
    type enumeration {
      enum "critical";
      enum "major";
      enum "minor";
    }
  }

  typedef alert-state {
    type enumeration {
      enum "raised" {
        description
          "Alert is raised";
      }
      enum "cleared" {
        description
          "Alert is cleared";
      }
      enum "error" {
        description
          "Alert is in error";
      }
    }
    description
      "Possible states of an alert";
  }

  typedef alert-comparator {
    description
      "defined comparator";
    type enumeration{
      enum "gt" {
        description
          "Greater than";
      }
      enum "lt" {
        description
          "Lesser than";
      }
      enum "gte" {
        description
          "Greater than equal";
      }
      enum "lte" {
        description
          "Lesser than equal";
      }
    }
  }

  typedef alert-metric-direction {
    type enumeration {
      enum "sd" {
        description
          "Source to destination: from sender to reflector";
      }
      enum "ds" {
        description
          "Destination to source: from reflector to sender";
      }
      enum "rt" {
        description
          "Round Trip: from sender to reflector then back to sender";
      }
    }
  }

  typedef alert-metric-delay-type {
    type enumeration {
      enum "delay-std-dev" {
        description
          "Delay standard deviation per period";
      }
      enum "delay-avg" {
        description
          "Delay average per period";
      }
      enum "delay-max" {
        description
          "Maximum delay per period";
      }
      enum "delay-min" {
        description
          "Minimum delay per period";
      }
      enum "delay-p95" {
        description
          "Delay 95th percentile per period";
      }
      enum "delay-p75" {
        description
          "Delay 75th percentile per period";
      }
      enum "delay-p50" {
        description
          "Delay 50th percentile per period";
      }
      enum "delay-p25" {
        description
          "Delay 25th percentile per period";
      }
      enum "delay-phi" {
        description
          "Delay 98th percentile per period";
      }
      enum "delay-plo" {
        description
          "Delay 96th percentile per period";
      }
      enum "delay-pmi" {
        description
          "Delay 98th percentile per period";
      }
      enum "delay-var-avg" {
        description
          "Average delay variation during the period";
      }
      enum "delay-var-max" {
        description
          "Maximum delay variation during the period";
      }
      enum "delay-var-min" {
        description
          "Minimum delay variation during the period";
      }
      enum "delay-var-p95" {
        description
          "Delay variation 95th percentile per period";
      }
      enum "delay-var-p75" {
        description
          "Delay variation 75th percentile per period";
      }
      enum "delay-var-p50" {
        description
          "Delay variation 50th percentile per period";
      }
      enum "delay-var-p25" {
        description
          "Delay variation 25th percentile per period";
      }
      enum "delay-var-phi" {
        description
          "Delay variation 99th percentile per period";
      }
      enum "delay-var-plo" {
        description
          "Delay variation 96th percentile per period";
      }
      enum "delay-var-pmi" {
        description
          "Delay variation 98th percentile per period";
      }
    }
  }

  typedef alert-metric-packetloss-type {
    type enumeration {
      enum "packets-lost-pct" {
        description
          "Packetloss ratio in percentage";
      }
      enum "packets-lost" {
        description
          "Total number of loss packets";
      }
    }
  }

  typedef alert-metric-jitter-type {
    type enumeration {
      enum "jitter-avg" {
        description
          "Average jitter per period";
      }
      enum "jitter-max" {
        description
          "Maximum jitter per period";
      }
      enum "jitter-min" {
        description
          "Minimum jitter per period";
      }
      enum "jitter-p95" {
        description
          "Jitter 95th percentile per period";
      }
      enum "jitter-p75" {
        description
          "Jitter 75th percentile per period";
      }
      enum "jitter-p50" {
        description
          "Jitter 50th percentile per period";
      }
      enum "jitter-p25" {
        description
          "Jitter 25th percentile per period";
      }
      enum "jitter-phi" {
        description
          "Jitter 99th percentile per period";
      }
      enum "jitter-plo" {
        description
          "Jitter 96th percentile per period";
      }
      enum "jitter-pmi" {
        description
          "Jitter 96th percentile per period";
      }
      enum "jitter-std-dev" {
        description
          "Jitter standard deviation per period";
      }
    }
  }

  typedef alert-metric-packets-type {
    type enumeration {
      enum "packets-duplicated" {
        description
          "Number of packets received duplicated per period";
      }
      enum "packets-misordered" {
        description
          "Number of packets received misordered per period";
      }
      enum "packets-received" {
        description
          "Number of packets received per period";
      }
      enum "packets-too-late" {
        description
          "Number of packets received too late per period";
      }
    }
  }

  typedef alert-metric-misc-type {
    type enumeration {
      enum "bytes-received" {
        description
          "Number of bytes received too late per period";
      }
      enum "congestion" {
        description
          "Congestion delay per period";
      }
      enum "ip-tosmax" {
        description
          "Maximum received TOS per period";
      }
      enum "ip-tosmin" {
        description
          "Minimum received TOS per period";
      }
      enum "lost-burst-max" {
        description
          "Longest loss length per period";
      }
      enum "lost-burst-min" {
        description
          "Shortest loss length per period";
      }
      enum "mos" {
        description
          "Mean opinion score per period";
      }
      enum "periods-lost" {
        description
          "The number of lost periods per interval";
      }
      enum "r-value" {
        description
          "Rating value per period";
      }
      enum "sync-quality" {
        description
          "Sync quality factor in percentage";
      }
      enum "ttl-max" {
        description
          "Maximum received TTL per period";
      }
      enum "ttl-min" {
        description
          "Minimum received TTL per period";
      }
      enum "vlan-pbit-max" {
        description
          "Maximum received VLAN priority per period";
      }
      enum "vlan-pbit-min" {
        description
          "Minimum received VLAN priority per period";
      }
    }
  }

  typedef alert-metric-type {
    type union {
      type alert-metric-delay-type;
      type alert-metric-packetloss-type;
      type alert-metric-jitter-type;
      type alert-metric-packets-type;
      type alert-metric-misc-type;
    }
  }

  grouping alert-metric-data {
    description
      "The data representing the current state of the metric alert";

    leaf type {
      type alert-metric-type;
      description
        "Metric type generating the alert";
    }

    leaf direction {
      type alert-metric-direction;
      description
        "Indicates the direction of the metric triggering the alert";
    }

    leaf value {
      type string;
      description
        "The value triggering the alert condition.
        The type of the value depends on the metric type";
    }
  }

  grouping alert-condition-data {
    description
      "The data representing the alert condition";

    leaf metric-type {
    type acdalt:alert-metric-type;
    mandatory true;
    description
      "The type of the metric on which this condition will apply";
    }

    leaf alert-direction {
    type acdalt:alert-metric-direction;
    default "sd";
    description
      "The traffic direction monitored by this condition";
    }

    leaf alert-severity {
    type acdalt:alert-severity;
    description
      "The severity of this alert condition. This severity
      will be passed back as-is to the yang client through
      the alert-notifications";
    }
  }
}
